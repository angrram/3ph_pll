# requierements

## #1: Output the Angle phase (Functional)
Read 3 phases and output the angle in a range of -pi to pi.

## #2: Output a Phase Fault (Container)
Take input the three phases and if unbalance or phase shift occurs output a error signal.

### #5: Phase Voltage Fault (Functional)
If at least one phases presents a sack (drop or amplitud increase) it should detect.

### #6: Phase shift Fault Detection (Functional)
If one or more phases lags the 120° degrees output an error signal.s

## #3: Phase swap detection (Functional)
Input the three phases and detect the phase swap
